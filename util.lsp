(defun sort (sett matrix / count i j key1 key2)
  (setq count (vla-get-count sett))
  (setq i 1)
  (while (< i count)
    (setq key1 (vlax-safearray-get-element matrix i 0)
	  key2 (vlax-safearray-get-element matrix i 1)
	  j (1- i))
    (while (and  (>= j 0) (> (atoi (vlax-safearray-get-element matrix j 1)) (atoi key2)))
      (vlax-safearray-put-element matrix (1+ j) 0 (vlax-safearray-get-element matrix j 0))
      (vlax-safearray-put-element matrix (1+ j) 1 (vlax-safearray-get-element matrix j 1))
      (setq j (1- j))
      )
    (vlax-safearray-put-element matrix (1+ j) 0 key1)
    (vlax-safearray-put-element matrix (1+ j) 1 key2)
    
    (setq i (1+ i))
    
    )
  (setq sortedarray matrix)
)

(defun get_start_end_core(str / pos start end)
  (setq pos (vl-string-search "-" str)
	start (substr str 1 pos)
	end (substr str (1+(1+ pos))))
  (list (atoi start) (atoi end))
  )

(defun c:getwago()
  (insertwago (getpoint "select insertion point of wago terminals") (getint "Enter start index") (getint "Enter Cable core required"))
  )

(defun c:tosheet()
  (insertblocks 1 (getpoint "select insertion point") (list (getstring "Enter Alphabet") (strcat "(TO SHT."  (getstring "Enter TO page No") ")")))
  )

(defun c:fromsheet()
  (insertblocks 2 (getpoint "select insertion point") (list (getstring "Enter Alphabet") (strcat "(FROM SHT."  (getstring "Enter FROM page No") ")")))
  )

(defun c:dinrail()
  (insertblocks 3 (getpoint "select insertion point") (list (getstring "Enter COLUMN name") ))
  )

(defun c:endstopper()
  (insertblocks 4 (getpoint "select insertion point") (list))
  )

(defun insertwago(blk_pt start core)
  	(setq 
	blk_x_pt (nth 0 blk_pt)
	blk_y_pt (nth 1 blk_pt)
	temp_y blk_y_pt
	index 1)
  (while (<= index core)
    (if (< start 10) (setq txt (strcat "0" (rtos start 2 0))) (setq txt (rtos start 2 0) ) )
  (setq wref (vla-InsertBlock modelSpace (vlax-3d-point blk_x_pt temp_y 0) (findfile (strcat root_drive ":\\auto_edrc_s&t\\Outdoor Automation\\Database\\blocks\\wago.dwg"))
      1
      1
      1
      0
    ))
    (vla-explode wref)
    (setq textpoint (vlax-3d-point (- blk_x_pt 2.1881) (- temp_y 1.8667) 0))

       (setq textobj(vla-Addmtext modelspace textpoint 5 txt ))
       (vla-put-height textobj 1.7)
       (vla-put-attachmentpoint textobj 5)
       (vla-put-insertionpoint textObj textpoint)
       (vla-put-stylename textobj "ROMANS")

    (setq start (1+ start))
    (setq temp_y (- temp_y 3.1436))
    (setq index (1+ index))
  )
  (setq eref (vla-InsertBlock modelSpace (vlax-3d-point blk_x_pt temp_y 0) (findfile (strcat root_drive ":\\auto_edrc_s&t\\Outdoor Automation\\Database\\blocks\\endplate.dwg"))
      1
      1
      1
      0
    ))
  (vla-explode eref)
  )


(defun insertblocks(token ins_pt data_list)
  (cond
    ( (= token 1)
		(setq bref (vla-InsertBlock modelSpace (vlax-3d-point (car ins_pt)  (cadr ins_pt) 0) (findfile (strcat root_drive ":\\auto_edrc_s&t\\Outdoor Automation\\Database\\blocks\\tosheet.dwg")) 1 1 1 0))
		
		(setq textpoint (vlax-3d-point (car ins_pt) (- (cadr ins_pt) 9) 0))
		(setq textobj(vla-Addmtext modelspace textpoint 5 (car data_list) ))
		(vla-put-height textobj 2.2)
		(vla-put-attachmentpoint textobj 5)
		(vla-put-insertionpoint textObj textpoint)
		(vla-put-stylename textobj "ROMANS")

		(setq textpoint (vlax-3d-point (car ins_pt) (- (cadr ins_pt) 15) 0))
		(setq textobj(vla-Addmtext modelspace textpoint 30 (cadr data_list) ))
		(vla-put-height textobj 2.2)
		(vla-put-attachmentpoint textobj 5)
		(vla-put-insertionpoint textObj textpoint)
		(vla-put-stylename textobj "ROMANS")
		)
    ( (= token 2)
		(setq bref (vla-InsertBlock modelSpace (vlax-3d-point (car ins_pt) (+ 6 (cadr ins_pt)) 0) (findfile (strcat root_drive ":\\auto_edrc_s&t\\Outdoor Automation\\Database\\blocks\\fromsheet.dwg")) 1 1 1 0))
		
		(setq textpoint (vlax-3d-point (car ins_pt) (+ 6 (+ (cadr ins_pt) 9)) 0))
		(setq textobj(vla-Addmtext modelspace textpoint 5 (car data_list) ))
		(vla-put-height textobj 2.2)
		(vla-put-attachmentpoint textobj 5)
		(vla-put-insertionpoint textObj textpoint)
		(vla-put-stylename textobj "ROMANS")

		(setq textpoint (vlax-3d-point (car ins_pt) (+ 6 (+ (cadr ins_pt) 15)) 0))
		(setq textobj(vla-Addmtext modelspace textpoint 30 (cadr data_list) ))
		(vla-put-height textobj 2.2)
		(vla-put-attachmentpoint textobj 5)
		(vla-put-insertionpoint textObj textpoint)
		(vla-put-stylename textobj "ROMANS")
		)
    ( (= token 3)
		(setq bref (vla-InsertBlock modelSpace (vlax-3d-point (car ins_pt) (cadr ins_pt) 0) (findfile (strcat root_drive ":\\auto_edrc_s&t\\Outdoor Automation\\Database\\blocks\\dinrail.dwg")) 1 1 1 0))
		
		(setq textpoint (vlax-3d-point (car ins_pt)  (+ (cadr ins_pt) 3) 0))
		(setq textobj(vla-Addmtext modelspace textpoint 5 (car data_list) ))
		(vla-put-height textobj 3)
		(vla-put-attachmentpoint textobj 5)
		(vla-put-insertionpoint textObj textpoint)
		(vla-put-stylename textobj "ROMANT")
     		(vla-explode bref)
    )
    ( (= token 4)
		(setq bref (vla-InsertBlock modelSpace (vlax-3d-point (car ins_pt) (cadr ins_pt) 0) (findfile (strcat root_drive ":\\auto_edrc_s&t\\Outdoor Automation\\Database\\blocks\\endstopper.dwg")) 1 1 1 0))
    )
    ((= token 5)
     		(setq core_type (rtos (get_wago_required (nth 1 data_list)) 2 0)
		      from_to (nth 3 data_list)
		      bracket_name (strcat core_type from_to ".dwg")
		      attr1 (strcat (nth 0 data_list) "(" (nth 1 data_list) ")")
		      attr2 (strcat "(" (nth 4 data_list) from_to " " (nth 2 data_list) ")"))
     		(setq bref (vla-InsertBlock modelSpace (vlax-3d-point (car ins_pt) (cadr ins_pt) 0) (findfile (strcat root_drive ":\\auto_edrc_s&t\\Outdoor Automation\\Database\\blocks\\brackets\\" bracket_name)) 1 1 1 0))
     		(setq varAttributes (vlax-variant-value (vla-GetAttributes bref)))
  		(vla-put-TextString (vlax-safearray-get-element varAttributes 0) attr1)
     		(vla-put-TextString (vlax-safearray-get-element varAttributes 1) attr2)
     		(vlax-put-property (car (vlax-safearray->list varAttributes)) 'height 2)
     		(vlax-put-property (cadr (vlax-safearray->list varAttributes)) 'height 2)
     	)
  )
)

(defun get_quad_range(core_string / index Lowest Highest L R )
  (setq index 1
	Lowest 25
	Highest 0)
  (while (<= index 6)
    (if (/= (vl-string-search  (strcat "Q" (rtos index 2 0)) core_string) nil)
     (progn  (setq lr (- (* index 4) 3))
       (if (< lr Lowest) (setq Lowest lr))
    (if (> (+ lr 3) Highest) (setq Highest (+ lr 3)))
       )
      )
    
    (if (/= (vl-string-search  (strcat "Q" (rtos index 2 0)) core_string) nil)
      (progn 
    (if (/= (vl-string-search  "(" core_string (vl-string-search  (strcat "Q" (rtos index 2 0)) core_string)) nil)
      (progn 
    	(setq L (+ (- (atoi (substr core_string (+ 2 (vl-string-search  "(" core_string)) 1)) 1) lr))
    	(setq R (+ (- (atoi (substr core_string  (vl-string-search  ")" core_string)  1)) 1) lr))
	(setq Highest R)
	(setq Lowest L)
    	(setq occupancy (strcat (rtos L 2 0) "-" (rtos R 2 0)))
    	)
      (progn
	(setq occupancy (strcat (rtos Lowest 2 0) "-" (rtos Highest 2 0)))
	)
	  ) ))
	
     (setq index (1+ index))
    )
  occupancy
  )

(defun processtext(str / pos 2pos 3pos 4pos fromto)
(setq ;str "06E(12CX1.5) (JB10-JB12)"
      pos (vl-string-search "(" str)
      2pos (vl-string-search ")" str (1+ pos))
      3pos (vl-string-search "(" str (1+ 2pos))
      4pos (vl-string-search ")" str (1+ 3pos))
      cableNo (substr str 1 pos)
      corage (substr str (1+(1+ pos)) (- (- 2pos pos) 1))
      fromto (substr str (1+(1+ 3pos)) (- (- 4pos 3pos) 1))
      pos (vl-string-search "-" fromto)
      from (substr fromto 1 pos)
      to (substr fromto (1+(1+ pos))))
  )

(defun get_tail_core (str)
  (setq	pos (vl-string-search "C" str))
  (substr str 1 pos)
  )

(defun putmtext(text pt width height style attach_type / textobj)
  (setq textobj(vla-Addmtext modelspace pt width text ))
  (vla-put-height textobj height)
  (vla-put-attachmentpoint textobj attach_type)
  (vla-put-insertionpoint textObj pt)
  (vla-put-stylename textobj style)
  )

(defun c:check_bracket()
  (setq core (getstring "core" ))
  (insertblocks 5 (list 0 0) (list "55A" (STRCAT CORE "CX1.5") "L8" "FROM"))
  (insertblocks 5 (list 0 0) (list "55A" (STRCAT CORE "CX1.5") "L8" "TO"))
  )
(defun findcells(flist clist / index maxi return)
  (setq return 1
	index 0)
  (foreach key flist
    (if (= key "SPARE")
      (PROGN
	(setq maxi (car (get_start_end_core (nth index clist))))
	(if (< return maxi)
	  (setq return maxi)
	  )
      )
    )
    (setq index (1+ index))
  )
  (setq return (1- return))
  )

(defun c:toloopcable()
  (setq ins_pt (getpoint "Select insertion point")
	cells (getint "Number of cells required")
	core (getint "Enter cable core"))
  (tocable ins_pt cells core)
  )
(defun tocable(ins_pt cells core /  x_pt y_pt temp_y spare textpoint textobj x2)
  (setq x_pt (nth 0 ins_pt)
	y_pt (nth 1 ins_pt)
	temp_y y_pt
	spare (- core cells))
  (vla-addline modelspace (vlax-3d-point x_pt y_pt 0) (vlax-3d-point (+ 27.5 x_pt) y_pt 0))
  (vla-addline modelspace (vlax-3d-point x_pt y_pt 0) (vlax-3d-point x_pt (- y_pt (* core 3.1436)) 0))
  (vla-addline modelspace (vlax-3d-point (+ x_pt 27.5) y_pt 0) (vlax-3d-point (+ 27.5 x_pt) (- y_pt (* core 3.1436)) 0))
  (vla-addline modelspace (vlax-3d-point x_pt (- y_pt (* core 3.1436)) 0) (vlax-3d-point (+ 27.5 x_pt) (- y_pt (* core 3.1436)) 0))
  (vla-addline modelspace (vlax-3d-point (+ x_pt 22) y_pt 0) (vlax-3d-point (+ x_pt 22) (- y_pt (* core 3.1436)) 0))
  (while (> cells 0)
    (setq temp_y (- temp_y 3.1436))
    (vla-addline modelspace (vlax-3d-point x_pt temp_y 0) (vlax-3d-point (+ 22 x_pt) temp_y 0))
    (setq cells (1- cells))
    )
  (setq textpoint (vlax-3d-point (+ x_pt 11) (- temp_y (* 0.5 (* 3.1436 spare))) 0))
  	(setq textobj(vla-Addmtext modelspace textpoint 5 "SPARE" ))
  	(vla-put-height textobj 2)
       (vla-put-attachmentpoint textobj 5)
       (vla-put-insertionpoint textObj textpoint)
       (vla-put-stylename textobj "ROMANS")
  (setq temp_y y_pt
	x2 (+ x_pt 22))
  (while (> core 0)
    (setq textpoint (vlax-3d-point (+ x2 (* 0.5 5.5)) (- temp_y (* 0.5 3.1436)) 0))
  	(setq textobj(vla-Addmtext modelspace textpoint 5 "-" ))
  	(vla-put-height textobj 2)
       (vla-put-attachmentpoint textobj 5)
       (vla-put-insertionpoint textObj textpoint)
       (vla-put-stylename textobj "ROMANS")
    (setq temp_y (- temp_y 3.1436))
    (vla-addline modelspace (vlax-3d-point x2 temp_y 0) (vlax-3d-point (+ 5.5 x2) temp_y 0))
    (setq core (1- core))
    )
       
)
(defun c:fromloopcable()
  (setq ins_pt (getpoint "Select insertion point")
	cells (getint "Number of cells required")
	core (getint "Enter cable core"))
  (fromcable ins_pt cells core)
  )
(defun fromcable(ins_pt cells core / x_pt y_pt temp_y spare textpoint textobj x2)
  (setq x_pt (nth 0 ins_pt)
	y_pt (nth 1 ins_pt)
	temp_y y_pt
	spare (- core cells))
  (vla-addline modelspace (vlax-3d-point x_pt y_pt 0) (vlax-3d-point (+ 27.5 x_pt) y_pt 0))
  (vla-addline modelspace (vlax-3d-point x_pt y_pt 0) (vlax-3d-point x_pt (- y_pt (* core 3.1436)) 0))
  (vla-addline modelspace (vlax-3d-point (+ x_pt 27.5) y_pt 0) (vlax-3d-point (+ 27.5 x_pt) (- y_pt (* core 3.1436)) 0))
  (vla-addline modelspace (vlax-3d-point x_pt (- y_pt (* core 3.1436)) 0) (vlax-3d-point (+ 27.5 x_pt) (- y_pt (* core 3.1436)) 0))
  (vla-addline modelspace (vlax-3d-point (+ x_pt 5.5) y_pt 0) (vlax-3d-point (+ x_pt 5.5) (- y_pt (* core 3.1436)) 0))
  (while (> cells 0)
    (setq temp_y (- temp_y 3.1436))
    (vla-addline modelspace (vlax-3d-point (+ 5.5 x_pt) temp_y 0) (vlax-3d-point (+ 27.5 x_pt) temp_y 0))
    (setq cells (1- cells))
    )
  (setq textpoint (vlax-3d-point (+ x_pt 16.5) (- temp_y (* 0.5 (* 3.1436 spare))) 0))
  	(setq textobj(vla-Addmtext modelspace textpoint 5 "SPARE" ))
  	(vla-put-height textobj 2)
       (vla-put-attachmentpoint textobj 5)
       (vla-put-insertionpoint textObj textpoint)
       (vla-put-stylename textobj "ROMANS")
  (setq temp_y y_pt
	x2 x_pt)
  (while (> core 0)
    (setq textpoint (vlax-3d-point (+ x2 (* 0.5 5.5)) (- temp_y (* 0.5 3.1436)) 0))
  	(setq textobj(vla-Addmtext modelspace textpoint 5 "-" ))
  	(vla-put-height textobj 2)
       (vla-put-attachmentpoint textobj 5)
       (vla-put-insertionpoint textObj textpoint)
       (vla-put-stylename textobj "ROMANS")
    (setq temp_y (- temp_y 3.1436))
    (vla-addline modelspace (vlax-3d-point x2 temp_y 0) (vlax-3d-point (+ 5.5 x2) temp_y 0))
    (setq core (1- core))
    )
       
)

(defun c:loop( / ins_pt x_pt y_pt row tofrom start end textpoint textobj str)
  (setq ins_pt(getpoint "Select insertion point")
	x_pt (nth 0 ins_pt)
	y_pt (nth 1 ins_pt)
	row(getstring "Select row name")
	tofrom(getstring "Type either TO or FROM")
	start(getint "select start wagoindex")
	end(getint "select end wago index")
	)
  (while (<= start end)
    (if (< start 10 )(setq str (strcat "0" (rtos start 2 0 ))) (setq str  (rtos start 2 0 )) )
    (setq textpoint (vlax-3d-point (+ x_pt 11) (- y_pt (* 0.5 3.1436)) 0))
  	(setq textobj(vla-Addmtext modelspace textpoint 20 (strcat tofrom " " row str) ))
  	(vla-put-height textobj 2)
       (vla-put-attachmentpoint textobj 5)
       (vla-put-insertionpoint textObj textpoint)
       (vla-put-stylename textobj "ROMANS")
    (setq y_pt (- y_pt 3.1436)
	  start (1+ start))
    
    )
  )

(defun str->list (str delim / ptr lst)
(while (setq ptr (vl-string-search delim str))
(setq lst (cons (substr str 1 ptr) lst))
(setq str (substr str (+ ptr 2)))
)
(reverse (cons str lst))
)

(defun c:drawdashes()
  (dash (getpoint "Please choose the ins_point") (getint "Please enter number of cores"))
  )

(defun c:drawcores()
  (draw_core_numbers (getpoint "Please choose the ins_point") (getint "Please enter number of cores"))
  )

(defun dash(ins_pt core)
  (setq x2 (car ins_pt)
	temp_y (cadr ins_pt))
  (while (> core 0)
    (setq textpoint (vlax-3d-point (+ x2 (* 0.5 5.5)) (- temp_y (* 0.5 3.1436)) 0))
  	(setq textobj(vla-Addmtext modelspace textpoint 5 "-" ))
  	(vla-put-height textobj 2)
       (vla-put-attachmentpoint textobj 5)
       (vla-put-insertionpoint textObj textpoint)
       (vla-put-stylename textobj "ROMANS")
    (setq temp_y (- temp_y 3.1436))
    (vla-addline modelspace (vlax-3d-point x2 temp_y 0) (vlax-3d-point (+ 5.5 x2) temp_y 0))
    (setq core (1- core))
    )
  )

(defun c:a1b2( / fset f a1 b2 ins_pt )
  (alert "please select functions to reach relay")
  (setq selectionset_count (vla-get-count (vla-get-SelectionSets doc) ))
  (while (> selectionset_count 0)
    (vla-delete (vla-item (vla-get-SelectionSets doc) 0))
    (setq selectionset_count (1- selectionset_count)))
  (setq fset (vla-Add (vla-get-SelectionSets doc) "fun"))
  (vla-SelectOnScreen fset)
  (setq f (vla-get-TextString (vla-Item fset 0)))
  (setq ins_pt (getpoint "please select Insertion point"))
  (put_a1b2 f ins_pt)
  )

(defun put_a1b2(f ins_pt / a1 b2)
  
  (cond
    ((and (= (substr f (strlen f)) "G") (vl-string-search "AMG" f) )
     (setq a1 (strcat "A1 " (substr f 1 (1- (strlen f))) "HPR"))
     (setq b2 (strcat "B2 " (substr f 1 (1- (strlen f))) "HPR"))
    )
    ((= (substr f (strlen f)) "G")
     (setq a1 (strcat "A1 " (substr f 1 (1- (strlen f))) "PR"))
     (setq b2 (strcat "B2 " (substr f 1 (1- (strlen f))) "PR"))
    )
    ((= (substr f 1 2) "SH")
     (setq a1 (strcat "A1 " (car (str->list f " ")) " HPR"))
     (setq b2 (strcat "B2 " (car (str->list f " ")) " HPR"))
    )
  )
  (putmtext a1 (vlax-3d-point (+ (car ins_pt) 11) (- (cadr ins_pt) (* 0.5 3.1436)) 0) 25 2 "ROMANS" 5)
  (putmtext b2 (vlax-3d-point (+ (car ins_pt) 11) (- (cadr ins_pt) (* 1.5 3.1436)) 0) 25 2 "ROMANS" 5)
  )

(defun c:a2b1( / fset f a2 b1 ins_pt )
  (alert "please select functions to reach field")
  (setq selectionset_count (vla-get-count (vla-get-SelectionSets doc) ))
  (while (> selectionset_count 0)
    (vla-delete (vla-item (vla-get-SelectionSets doc) 0))
    (setq selectionset_count (1- selectionset_count)))
  (setq fset (vla-Add (vla-get-SelectionSets doc) "fun"))
  (vla-SelectOnScreen fset)
  (setq f (vla-get-TextString (vla-Item fset 0)))
  (setq ins_pt (getpoint "please select Insertion point"))
  (put_a2b1 f ins_pt)
  )
(defun put_a2b1(f ins_pt / a1 b2)
  
  (cond
    ((and (= (substr f (strlen f)) "G") (vl-string-search "AMG" f) )
     (setq a2 (strcat "A2 " (substr f 1 (1- (strlen f))) "HPR"))
     (setq b1 (strcat "B1 " (substr f 1 (1- (strlen f))) "HPR"))
    )
    ((= (substr f (strlen f)) "G")
     (setq a2 (strcat "A2 " (substr f 1 (1- (strlen f))) "PR"))
     (setq b1 (strcat "B1 " (substr f 1 (1- (strlen f))) "PR"))
    )
    ((= (substr f 1 2) "SH")
     (setq a2 (strcat "A2 " (car (str->list f " ")) " HPR"))
     (setq b1 (strcat "B1 " (car (str->list f " ")) " HPR"))
    )
  )
  (putmtext a2 (vlax-3d-point (+ (car ins_pt) 11) (- (cadr ins_pt) (* 0.5 3.1436)) 0) 25 2 "ROMANS" 5)
  (putmtext b1 (vlax-3d-point (+ (car ins_pt) 11) (- (cadr ins_pt) (* 1.5 3.1436)) 0) 25 2 "ROMANS" 5)
  )

(defun c:r1r2( / fset f r1 r2 ins_pt )
  (alert "please select functions to reach relay")
  (setq selectionset_count (vla-get-count (vla-get-SelectionSets doc) ))
  (while (> selectionset_count 0)
    (vla-delete (vla-item (vla-get-SelectionSets doc) 0))
    (setq selectionset_count (1- selectionset_count)))
  (setq fset (vla-Add (vla-get-SelectionSets doc) "fun"))
  (vla-SelectOnScreen fset)
  (setq f (vla-get-TextString (vla-Item fset 0)))
  (setq ins_pt (getpoint "please select Insertion point"))
  (put_r1r2 f ins_pt)
  )

(defun put_r1r2(f ins_pt)
  (setq r1 (strcat "R1 " f))
  (setq r2 (strcat "R2 " f))
  (putmtext r2 (vlax-3d-point (+ (car ins_pt) 11) (- (cadr ins_pt) (* 1.5 3.1436)) 0) 25 2 "ROMANS" 5)
  (putmtext r1 (vlax-3d-point (+ (car ins_pt) 11) (- (cadr ins_pt) (* 0.5 3.1436)) 0) 25 2 "ROMANS" 5)
  )

(defun c:tolv( / fset f r1 r2 ins_pt )
  (alert "please select functions to reach LV")
  (setq selectionset_count (vla-get-count (vla-get-SelectionSets doc) ))
  (while (> selectionset_count 0)
    (vla-delete (vla-item (vla-get-SelectionSets doc) 0))
    (setq selectionset_count (1- selectionset_count)))
  (setq fset (vla-Add (vla-get-SelectionSets doc) "fun"))
  (vla-SelectOnScreen fset)
  (setq f (vla-get-TextString (vla-Item fset 0)))
  (setq ins_pt (getpoint "please select Insertion point"))
  (put_tolv f ins_pt)
  )

(defun put_tolv(f ins_pt)
  (setq lv (strcat "TO LV-" f))
  (putmtext lv (vlax-3d-point (+ (car ins_pt) 11) (- (cadr ins_pt) 3.1436) 0) 25 2 "ROMANS" 5)
  )

(defun c:tailbracket()
  (setq core (getstring "Enter core_number (for example 12 or 16)")
	bracket_name (strcat core "TO.dwg")
	cable_name(getstring "Please enter core details (for example QUAD or 12CX1.5Sqmm)")
	cable_to (getstring "Plase enter cable gear details")
	ins_pt (getpoint "please select insertion point"))
  (setq bref (vla-InsertBlock modelSpace (vlax-3d-point (car ins_pt) (cadr ins_pt) 0) (findfile (strcat root_drive ":\\auto_edrc_s&t\\Outdoor Automation\\Database\\blocks\\brackets\\" bracket_name)) 1 1 1 0))
     		(setq varAttributes (vlax-variant-value (vla-GetAttributes bref)))
  		(vla-put-TextString (vlax-safearray-get-element varAttributes 0) cable_name)
     		(vla-put-TextString (vlax-safearray-get-element varAttributes 1) cable_to)
     		(vlax-put-property (car (vlax-safearray->list varAttributes)) 'height 2)
     		(vlax-put-property (cadr (vlax-safearray->list varAttributes)) 'height 2)
  
  )

(defun loopifleftsignal(f ins_pt)
  
  (setq ins_pt (list(+ (car ins_pt) 41) (cadr ins_pt) 0))
  (setq pr (vl-string-search "PR" f)
	s (substr f 1 1)
	e (substr f (strlen f)))
  (cond
    ((/= pr nil)
     (put_r1r2 f ins_pt)
     )
    ((and (or (= s "S") (= s "C") (= s "D")) (or (= e "G")(= e "F")) (= (vl-string-search "RG" f) nil))
     (put_a1b2 f ins_pt)
     )
    )
  )
(defun loopifrightsignal(f ins_pt)
  (setq ins_pt (list(- (car ins_pt) 41) (cadr ins_pt) 0))
  (setq pr (vl-string-search "PR" f)
	s (substr f 1 1)
	e (substr f (strlen f)))
  (cond
    ((and (or (= s "S") (= s "C") (= s "D")) (or (= e "G")(= e "F")) (= (vl-string-search "RG" f) nil))
     (put_a2b1 f ins_pt)
     )
    )
  )
