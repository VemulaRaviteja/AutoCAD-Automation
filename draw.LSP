(defun c:arrangecables()
  (setq loc (getstring "Enter Location Name ( for example LOC-20A or JB-8 ) "))
  (loaddialog loc)
  (setq column_a_cables (list )
	column_b_cables (list )
	column_c_cables (list )
	column_d_cables (list ))
  )

(defun c:buildlocation()
  (setq loc (getstring "Enter Location Name ( for example LOC-20A or JB-8 ) "))
  
  (GetExcel (strcat root_drive ":\\auto_edrc_s&t\\Outdoor Automation\\Database\\excel\\" STATION ".xlsx") loc "Z2")
  (GetExcel (strcat root_drive ":\\auto_edrc_s&t\\Outdoor Automation\\Database\\excel\\" STATION ".xlsx") loc (strcat "Z" (getcell "Z2")))
  (build_dinrail "A" (list 0 0) (str->list (getcell "Z3") " ") "a")
  (build_dinrail "B" (list 98 0) (str->list (getcell "Z4") " ") "b")
  (build_dinrail "C" (list (* 2 98) 0) (str->list (getcell "Z5") " ") "c")
  (build_dinrail "D" (list (* 3 95) 0) (str->list (getcell "Z6") " ") "d")
  )

(defun build_dinrail (col_name ins_pt cab_order over_flow)
  (setq sheet 1
	dinrail_start 1
	v_level (cadr ins_pt)
	v_level_fixed v_level
	h_level (car ins_pt)
	cab_index 1
	)
  (acet-ui-progress-init (strcat "Terminating  all  the  cables  in  dinrail  " col_name) (length cab_order))
  (setq v_level (draw_header h_level v_level 1 col_name))
  (foreach cab cab_order
    (acet-ui-progress-safe cab_index)
    (setq unique_id (getcell (strcat "E" cab))
	  wago_required (get_wago_required (getcell (strcat "B" cab))))
    (if (= (is_space_available v_level wago_required) "false")
      (progn
	(insertblocks 1 (list h_level v_level) (list over_flow "TO SHT.301"))
      (setq sheet (1+ sheet)
	    h_level (+ h_level (+ template_width sheet_spacing))
	    v_level v_level_fixed)
	(insertblocks 2 (list h_level v_level) (list over_flow "FROM SHT.300"))
	(setq v_level (draw_header h_level v_level 0 col_name))
      )
     )
    (cond
      ((= unique_id "1")
       (setq v_level (draw_left_cable cab h_level v_level))
       (setq dinrail_start (+ dinrail_start wago_required))
      )
      ((= unique_id "2")
       (setq v_level (draw_right_cable cab h_level v_level))
       (setq dinrail_start (+ dinrail_start wago_required))
      )
      ((or (= unique_id "3") (= unique_id "5"))
       (setq v_level (draw_left_right_cable cab h_level v_level))
       (setq dinrail_start (+ dinrail_start wago_required))
      )
      ((= unique_id "4")
       (if (= (vl-string-search "QUAD" (getcell (strcat "B" cab))) nil)
	 (progn 
       (setq v_level (draw_tail_cable cab h_level v_level)))
	 (progn
	   (setq v_level (draw_right_cable cab h_level v_level))
	   )
	 )
       (setq dinrail_start (+ dinrail_start wago_required))
      )
    )
    (setq cab_index (1+ cab_index))
    )
  (draw_footer h_level v_level)
  (acet-ui-progress-done)
  )

(defun draw_header(h v es_req name / return)
  (setq x1 (- h 37)
	x2 (+ h 9.5))
  (insertblocks 3 (list h v) (list name))
  (setq v (- v (cadr dinrail_dim)))
  (if (= es_req 1)
    (progn (insertblocks 4 (list h v) (list))
    (setq v (- v (cadr end_stopper_dim))))
    )
  (vla-addline modelspace (vlax-3d-point x1 v 0) (vlax-3d-point (+ x1 27.5) v 0))
  (vla-addline modelspace (vlax-3d-point (+ x1 27.5) v 0) (vlax-3d-point (+ x1 27.5) (+ v 6.2872) 0))
  (vla-addline modelspace (vlax-3d-point (+ x1 27.5) (+ v 6.2872) 0) (vlax-3d-point x1 (+ v 6.2872) 0))
  (vla-addline modelspace (vlax-3d-point x1 (+ v 6.2872) 0) (vlax-3d-point x1 v 0))
  (vla-addline modelspace (vlax-3d-point (+ 5.5 x1) v 0) (vlax-3d-point (+ x1 5.5) (+ 6.2872 v) 0))

  (vla-addline modelspace (vlax-3d-point x2 v 0) (vlax-3d-point (+ x2 27.5) v 0))
  (vla-addline modelspace (vlax-3d-point (+ x2 27.5) v 0) (vlax-3d-point (+ x2 27.5) (+ v 6.2872) 0))
  (vla-addline modelspace (vlax-3d-point (+ x2 27.5) (+ v 6.2872) 0) (vlax-3d-point x2 (+ v 6.2872) 0))
  (vla-addline modelspace (vlax-3d-point x2 (+ v 6.2872) 0) (vlax-3d-point x2 v 0))
  (vla-addline modelspace (vlax-3d-point (+ 22 x2) v 0) (vlax-3d-point (+ x2 22) (+ 6.2872 v) 0))

  (setq textpoint (vlax-3d-point (+ x1 16.5) (+ v 3.1436) 0))
		(setq textobj(vla-Addmtext modelspace textpoint 20 "FUNCTION" ))
		(vla-put-height textobj 2)
		(vla-put-attachmentpoint textobj 5)
		(vla-put-insertionpoint textObj textpoint)
		(vla-put-stylename textobj "ROMANS")
  (setq textpoint (vlax-3d-point (+ x1 2.75) (+ v 3.1436) 0))
		(setq textobj(vla-Addmtext modelspace textpoint 5  "C.\nNO."))
		(vla-put-height textobj 2)
		(vla-put-attachmentpoint textobj 5)
		(vla-put-insertionpoint textObj textpoint)
		(vla-put-stylename textobj "ROMANS")
  (setq textpoint (vlax-3d-point (+ x2 11) (+ v 3.1436) 0))
		(setq textobj(vla-Addmtext modelspace textpoint 20 "FUNCTION" ))
		(vla-put-height textobj 2)
		(vla-put-attachmentpoint textobj 5)
		(vla-put-insertionpoint textObj textpoint)
		(vla-put-stylename textobj "ROMANS")
  (setq textpoint (vlax-3d-point (+ x2 24.75) (+ v 3.1436) 0))
		(setq textobj(vla-Addmtext modelspace textpoint 5 "C.\nNO."))
		(vla-put-height textobj 2)
		(vla-put-attachmentpoint textobj 5)
		(vla-put-insertionpoint textObj textpoint)
		(vla-put-stylename textobj "ROMANS")
  (setq return v)
  return
 )

(defun draw_footer(h v / bref )
    (insertblocks 4 (list h v) (list))
    (setq v (- v (cadr end_stopper_dim)))
  (setq bref (vla-InsertBlock modelSpace (vlax-3d-point h v 0) (findfile (strcat root_drive ":\\auto_edrc_s&t\\Outdoor Automation\\Database\\blocks\\dinrail.dwg")) 1 1 1 0))
  (vla-explode bref)
 )

(defun get_wago_required(str / core)
  (setq core 12)
  (if (/= (vl-string-search "C" str) nil)
    (setq core (atoi (substr str 1 (vl-string-search "C" str))))
    )
  (if (/= (vl-string-search "Q" str) nil)
    (setq core (* 4 (atoi (substr str 1 (vl-string-search "Q" str)))))
    )
  core
  )

(defun is_space_available (v wago_count / return)
  (setq newlevel (abs (- v (* wago_count (cadr wago_dim)))))
  (if (> newlevel 175)
    (setq return "false")
    (setq return "true")
    )
  return
  )

(defun draw_left_cable (cab_row h v / column fun_list cor_list core x1 x2 dindex s_e space)
  (insertwago (list h v) dinrail_start (get_wago_required (getcell (strcat "B" cab_row))))
  (insertblocks 5 (list (- h 38) v) (list (getcell (strcat "A" cab_row)) (getcell (strcat "B" cab_row)) (getcell (strcat "C" cab_row)) "FROM" ""))
  (setq column "I"
	fun_list (list)
	cor_list (list)
	core (get_wago_required (getcell (strcat "B" cab_row))))
  (while (/= (getcell (strcat column cab_row)) "")
    (setq fun_list (append fun_list (list (getcell (strcat column cab_row))))
	  cor_list (append cor_list (list (getcell (strcat column (rtos (1+ (atoi cab_row)) 2 0)))))
	  column (chr (1+(ascii column))))
    )
  (setq cells (findcells fun_list cor_list))
  (tocable (list(+ h 9.5) v 0) cells core)
  (setq x1 (- h 37)
	x2 (+ x1 5.5)) 
  (draw_core_numbers (list x1 v) core)
  (vla-addline modelspace (vlax-3d-point x1 v 0) (vlax-3d-point (+ x1 27.5) v 0))
  (vla-addline modelspace (vlax-3d-point (+ x1 27.5) v 0) (vlax-3d-point (+ x1 27.5) (- v (* core (cadr wago_dim))) 0))
  (vla-addline modelspace (vlax-3d-point x1 v 0) (vlax-3d-point x1 (- v (* core (cadr wago_dim))) 0))
  (vla-addline modelspace (vlax-3d-point x2 v 0) (vlax-3d-point x2 (- v (* core (cadr wago_dim))) 0))
  (setq dindex 0)
  (foreach f fun_list
    (setq s_e (get_start_end_core (nth dindex cor_list))
	  space (* (cadr wago_dim) (1+ (- (cadr s_e) (car s_e)))))
    (loopifleftsignal f (list x2 v 0))
    (putmtext f (vlax-3d-point (+ x2 11) (- v (* space 0.5)) 0) 25 2 "ROMANS" 5)
    (setq v (- v space)
	  dindex (1+ dindex))
    (vla-addline modelspace (vlax-3d-point x2 v 0) (vlax-3d-point (+ x2 22) v 0))
    )
  (setq v (- v (cadr end_plate_dim)))
  v
  )

(defun draw_right_cable(cab_row h v / column fun_list cor_list core x1 x2 dindex s_e space)
  (insertwago (list h v) dinrail_start (get_wago_required (getcell (strcat "B" cab_row))))
  (insertblocks 5 (list (+ h 38) v) (list (getcell (strcat "A" cab_row)) (getcell (strcat "B" cab_row)) (getcell (strcat "D" cab_row)) "TO" ""))
  (setq column "I"
	fun_list (list)
	cor_list (list)
	core (get_wago_required (getcell (strcat "B" cab_row))))
  (while (/= (getcell (strcat column cab_row)) "")
    (setq fun_list (append fun_list (list (getcell (strcat column cab_row))))
	  cor_list (append cor_list (list (getcell (strcat column (rtos (1+ (atoi cab_row)) 2 0)))))
	  column (chr (1+(ascii column))))
    )
  (setq cells (findcells fun_list cor_list))
  (fromcable (list(- h 37) v 0) cells core)
  (setq x1 (+ h 9.5)
	x2 (+ x1 22))
  (draw_core_numbers (list x2 v) core)
  (vla-addline modelspace (vlax-3d-point x1 v 0) (vlax-3d-point (+ x1 27.5) v 0))
  (vla-addline modelspace (vlax-3d-point (+ x1 27.5) v 0) (vlax-3d-point (+ x1 27.5) (- v (* core (cadr wago_dim))) 0))
  (vla-addline modelspace (vlax-3d-point x1 v 0) (vlax-3d-point x1 (- v (* core (cadr wago_dim))) 0))
  (vla-addline modelspace (vlax-3d-point x2 v 0) (vlax-3d-point x2 (- v (* core (cadr wago_dim))) 0))

  (setq dindex 0)
  (foreach f fun_list
    (setq s_e (get_start_end_core (nth dindex cor_list))
	  space (* (cadr wago_dim) (1+ (- (cadr s_e) (car s_e)))))
    (setq textpoint (vlax-3d-point (+ x1 11) (- v (* space 0.5)) 0))
		(setq textobj(vla-Addmtext modelspace textpoint 25 f ))
		(vla-put-height textobj 2)
		(vla-put-attachmentpoint textobj 5)
		(vla-put-insertionpoint textObj textpoint)
		(vla-put-stylename textobj "ROMANS")
    (setq v (- v space)
	  dindex (1+ dindex))
    (vla-addline modelspace (vlax-3d-point x1 v 0) (vlax-3d-point (+ x1 22) v 0))
    )
  (setq v (- v (cadr end_plate_dim)))
  v
  )

(defun draw_left_right_cable(cab_row h v)
  (insertwago (list h v) dinrail_start (get_wago_required (getcell (strcat "B" cab_row))))
  (setq cable_names (getcell (strcat "A" cab_row))
	pos (vl-string-search "&" cable_names)
	from_cable_name(substr cable_names 1 pos)
	to_cable_name (substr cable_names (1+(1+ pos)) (strlen cable_names))
	id (getcell (strcat "E" cab_row)))
  (if (= id "5") (setq sp "SPARE; ") (setq sp ""))
  (insertblocks 5 (list (- h 38) v) (list from_cable_name (getcell (strcat "B" cab_row)) (getcell (strcat "C" cab_row)) "FROM" sp))
  (insertblocks 5 (list (+ h 38) v) (list to_cable_name (getcell (strcat "B" cab_row)) (getcell (strcat "D" cab_row)) "TO" sp))
  (setq column "I"
	fun_list (list)
	cor_list (list)
	core (get_wago_required (getcell (strcat "B" cab_row))))
  (while (/= (getcell (strcat column cab_row)) "")
    (setq fun_list (append fun_list (list (getcell (strcat column cab_row))))
	  cor_list (append cor_list (list (getcell (strcat column (rtos (1+ (atoi cab_row)) 2 0)))))
	  column (chr (1+(ascii column))))
    )
  (setq x1 (+ h 9.5)
	x2 (+ x1 22)
	x3 (- h 37)
	x4 (+ x3 5.5))
  (draw_core_numbers (list x2 v) core)
  (draw_core_numbers (list x3 v) core)
  (vla-addline modelspace (vlax-3d-point x1 v 0) (vlax-3d-point (+ x1 27.5) v 0))
  (vla-addline modelspace (vlax-3d-point (+ x1 27.5) v 0) (vlax-3d-point (+ x1 27.5) (- v (* core (cadr wago_dim))) 0))
  (vla-addline modelspace (vlax-3d-point x1 v 0) (vlax-3d-point x1 (- v (* core (cadr wago_dim))) 0))
  (vla-addline modelspace (vlax-3d-point x2 v 0) (vlax-3d-point x2 (- v (* core (cadr wago_dim))) 0))

  (vla-addline modelspace (vlax-3d-point x3 v 0) (vlax-3d-point (+ x3 27.5) v 0))
  (vla-addline modelspace (vlax-3d-point (+ x3 27.5) v 0) (vlax-3d-point (+ x3 27.5) (- v (* core (cadr wago_dim))) 0))
  (vla-addline modelspace (vlax-3d-point x3 v 0) (vlax-3d-point x3 (- v (* core (cadr wago_dim))) 0))
  (vla-addline modelspace (vlax-3d-point x4 v 0) (vlax-3d-point x4 (- v (* core (cadr wago_dim))) 0))
  (setq dindex 0)

  (foreach f fun_list
    (setq s_e (get_start_end_core (nth dindex cor_list))
	  space (* (cadr wago_dim) (1+ (- (cadr s_e) (car s_e)))))
    (setq textpoint (vlax-3d-point (+ x1 11) (- v (* space 0.5)) 0))
		(setq textobj(vla-Addmtext modelspace textpoint 25 f ))
		(vla-put-height textobj 2)
		(vla-put-attachmentpoint textobj 5)
		(vla-put-insertionpoint textObj textpoint)
		(vla-put-stylename textobj "ROMANS")
    (setq textpoint (vlax-3d-point (+ x4 11) (- v (* space 0.5)) 0))
		(setq textobj(vla-Addmtext modelspace textpoint 25 f ))
		(vla-put-height textobj 2)
		(vla-put-attachmentpoint textobj 5)
		(vla-put-insertionpoint textObj textpoint)
		(vla-put-stylename textobj "ROMANS")
    (setq v (- v space)
	  dindex (1+ dindex))
    (vla-addline modelspace (vlax-3d-point x1 v 0) (vlax-3d-point (+ x1 22) v 0))
    (vla-addline modelspace (vlax-3d-point x4 v 0) (vlax-3d-point (+ x4 22) v 0))
    )
  (setq v (- v (cadr end_plate_dim)))
  v
  )

(defun draw_tail_cable(cab_row h v / return x1 x2 wago_consumed index core_number temp_y column fun_list cor_list width_req)
  (insertwago (list h v) dinrail_start (get_wago_required (getcell (strcat "B" cab_row))))
  (setq x1 (+ h 9.5)
	x2 (+ x1 22)
	wago_consumed 0
	index 0
	core_number (get_wago_required (getcell (strcat "B" cab_row)))
	temp_y v)
  (draw_core_numbers (list x2 v) core_number)

  (setq column "I"
	fun_list (list)
	cor_list (list))
  (while (/= (getcell (strcat column cab_row)) "")
    (setq fun_list (append fun_list (list (getcell (strcat column cab_row))))
	  cor_list (append cor_list (list (getcell (strcat column (rtos (1+ (atoi cab_row)) 2 0)))))
	  column (chr (1+(ascii column))))
    )

  (vla-addline modelspace (vlax-3d-point x1 v 0) (vlax-3d-point (+ x1 27.5) v 0))
  (vla-addline modelspace (vlax-3d-point (+ x1 27.5) v 0) (vlax-3d-point (+ x1 27.5) (- v (* core_number (cadr wago_dim))) 0))
  (vla-addline modelspace (vlax-3d-point x1 v 0) (vlax-3d-point x1 (- v (* core_number (cadr wago_dim))) 0))
  (vla-addline modelspace (vlax-3d-point x2 v 0) (vlax-3d-point x2 (- v (* core_number (cadr wago_dim))) 0))

  (foreach i cor_list
    (if (/= i "")
      (progn
       (setq width_req (* (1+ (- (cadr (get_start_end_core i)) (car (get_start_end_core i)))) 3.1436))
       (setq wago_consumed (+ wago_consumed (1+ (- (cadr (get_start_end_core i)) (car (get_start_end_core i))))))
       
       (vla-addline modelspace (vlax-3d-point x1 (- temp_y width_req) 0) (vlax-3d-point (+ 22 x1) (- temp_y width_req) 0))
       (loopifrightsignal (nth index fun_list) (list x1 temp_y 0))
       
       (setq textpoint (vlax-3d-point (+ x1 11) (- temp_y (* 0.5 width_req)) 0))

       (setq textobj(vla-Addmtext modelspace textpoint 22 (nth index fun_list) ))
       (vla-put-height textobj 2)
       (vla-put-attachmentpoint textobj 5)
       (vla-put-insertionpoint textObj textpoint)
       (vla-put-stylename textobj "ROMANS")

       (if (= (nth index fun_list) "SPARE") (setq core_number (cadr (get_start_end_core i))) )

       (setq index (1+ index))
       (setq temp_y (- temp_y width_req))
       
       ))
    
      )
  (fromcable (list (- h 37) v 0) wago_consumed core_number)
  (vla-addline modelspace (vlax-3d-point x1 (- temp_y (* 3.1436 (- core_number wago_consumed))) 0) (vlax-3d-point (+ 22 x1) (- temp_y (* 3.1436 (- core_number wago_consumed))) 0))
  (setq textpoint (vlax-3d-point (+ x1 11) (- temp_y (* 0.5 (* 3.1436 (- core_number wago_consumed)))) 0))

       (setq textobj(vla-Addmtext modelspace textpoint 22 "SPARE" ))
       (vla-put-height textobj 2)
       (vla-put-attachmentpoint textobj 5)
       (vla-put-insertionpoint textObj textpoint)
       (vla-put-stylename textobj "ROMANS")
  (setq return ( - (- temp_y (* 3.1436 (- core_number wago_consumed))) (cadr end_plate_dim)))
  return
  )

(defun draw_core_numbers(ins_pt core / text x_pt temp_y)
  (setq text 1
	x_pt (car ins_pt)
	temp_y (cadr ins_pt))
  (while (<= text core)
    
    (if (<  text 10) (setq str (strcat "0" (rtos text 2 0))) (setq str (rtos text 2 0)) )

    (setq textpoint (vlax-3d-point (+ x_pt (* 0.5 5.5)) (- temp_y (* 0.5 3.1436)) 0))

       (setq textobj(vla-Addmtext modelspace textpoint 5 str ))
       (vla-put-height textobj 2)
       (vla-put-attachmentpoint textobj 5)
       (vla-put-insertionpoint textObj textpoint)
       (vla-put-stylename textobj "ROMANS")
    (setq text (1+ text))
    (setq temp_y (- temp_y 3.1436))
    (vla-addline modelspace (vlax-3d-point x_pt temp_y 0) (vlax-3d-point (+ 5.5 x_pt) temp_y 0))
    )
  )
